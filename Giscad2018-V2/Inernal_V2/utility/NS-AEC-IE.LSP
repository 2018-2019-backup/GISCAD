(DEFUN C:V()

(COMMAND "VALIDATE" )

)



(DEFUN C:XD()

(COMMAND "VBARUN" "XDATA" )

)

(DEFUN C:xp()

(COMMAND "VBARUN" "xp" )

)


(DEFUN C:RED()

(COMMAND "REFEDIT"  )

)



(DEFUN C:AN()

(COMMAND "VBARUN" "AssetNums" )

)

(DEFUN C:ROT()

(COMMAND "VBARUN" "ROT" )

)

(DEFUN C:hull()

(COMMAND "VBARUN" "myshape" )

)
